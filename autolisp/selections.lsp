; AutoCAD Selection Commands by Metin Şaylan (http://metinsaylan.com)
; (c) 2014 

(defun C:selAll(/ x type )
  (initget 128 "Line Polyline Circle Arc Text MText MUltileader Dimension Solid Region ALL")
  (setq x (getkword "Entity Type (Line/Polyline/Circle/Arc/Text/MText/MUltileader/Dimension/Solid/Region) <ALL>"))  
  (if (equal x "Line") (setq type (list "LINE")))   
  (if (equal x "Polyline") (setq type (list "POLYLINE")) ) 
  (if (equal x "Circle") (setq type (list "CIRCLE")) )   
  (if (equal x "Arc") (setq type (list "ARC")) )   
  (if (equal x "Text") (setq type (list "TEXT")) )  
  (if (equal x "MText") (setq type (list "MTEXT")) )  
  (if (equal x "MUltileader") (setq type (list "MULTILEADER")) )
  (if (equal x "Solid") (setq type (list "3DSOLID")) )  
  (if (equal x "Region") (setq type (list "REGION")) )  
  (if (equal x "Dimension") (setq type (list "DIMENSION")) )  
  (if (/= x Nil) 
    (progn 
      (apply 'ms:selEnt type) 
    )
  )
  (princ)
)

(defun C:selLines() (apply 'ms:selEnt (list "LINE")))
(defun C:selPlines() (apply 'ms:selEnt (list "POLYLINE")))
(defun C:selCircles() (apply 'ms:selEnt (list "CIRCLE")))
(defun C:selText() (apply 'ms:selEnt (list "TEXT")))
(defun C:selMtext() (apply 'ms:selEnt (list "MTEXT")))
(defun C:selMleader() (apply 'ms:selEnt (list "MULTILEADER")))
(defun C:selDim() (apply 'ms:selEnt (list "DIMENSION")))

(defun ms:selEnt(entTyp)
  (princ (strcat "\nSelecting all " entTyp ".." ))
  (if (setq mySel (ssget "X" (list (cons 0 entTyp ))))
    (progn                              
      (sssetfirst Nil mySel)
      (setq mySel Nil)
    ) 
    (princ (strcat "\nNo entity found for: " entTyp "."))
  )
  (princ)
)

(defun C:selColor()
	(setq clrNum (getint "Please enter color table Number: "))
	(if (setq mySel (ssget "X" (list (cons 62 clrNum ))))
		(progn                      
		  (sssetfirst Nil mySel)
		  (setq mySel Nil)
		  (setq clrNum Nil)
		)
		(princ (strcat "\nNo objects found using color " clrNum "."))
	)
	(princ)
)
(princ "\nType selall to select entities.")
(princ)

; selAll AutoCAD Selection Commands by Metin Şaylan (http://metinsaylan.com)
; (c) 2014
